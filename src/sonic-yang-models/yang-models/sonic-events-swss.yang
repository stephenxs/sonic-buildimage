module sonic-events-swss {
    namespace "http://github.com/sonic-net/sonic-events-swss";
    yang-version 1.1;
    prefix events-swss;

    import sonic-events-common {
        prefix evtcmn;
        revision-date 2022-12-01;
    }

    import sonic-types {
        prefix stypes;
    }

    import sonic-port {
        prefix port;
    }

    organization
        "SONiC";

    contact
        "SONiC";

    description
        "SONIC SWSS events";

    revision 2022-12-01 {
        description "SWSS alert events.";
    }

    container sonic-events-swss {
        container if-state {
            evtcmn:ALARM_SEVERITY_MINOR;

            description "
                Declares an event for i/f flap.
                The name of the flapping i/f and status are the only params.";

            leaf ifname {
                type string {
                    pattern 'Ethernet[0-9]{1,3}';
                }
                description "Interface name";
            }

            leaf status {
                type stypes:admin_status;
                description "Provides the status as up (true) or down (false)";
            }

            uses evtcmn:sonic-events-cmn;
        }

        container pfc-storm {
            evtcmn:ALARM_SEVERITY_MAJOR;

            description "
                Declares an event for PFC storm.
                The name of the i/f facing the storm is the only param.";

            leaf ifname {
                type string {
                    pattern 'Ethernet[0-9]{1,2}';
                }
                description "Interface name";
            }

            leaf queue_index {
                type uint8;
            }

            leaf queue_id {
                type uint64;
            }

            leaf port_id {
                type uint64;
            }

            leaf additional_info {
                type string {
                    pattern '[-a-zA-Z0-9_]+:[-a-zA-Z0-9_]+(\|{1}[-a-zA-Z0-9_]+:[-a-zA-Z0-9_]+)*';
                }
                description "Additional information to investigate PFC storm";
            }

            uses evtcmn:sonic-events-cmn;
        }

        container chk_crm_threshold {
            evtcmn:ALARM_SEVERITY_MAJOR;

            description "
                Declares an event for CRM threshold.";

            leaf percent {
                type uint8 {
                    range 0..100;
                }
                description "percentage used";
            }

            leaf used_cnt {
                type uint32;
            }

            leaf free_cnt {
                type uint32;
            }

            uses evtcmn:sonic-events-cmn;
        }

        container select-operation-failure {
            evtcmn:ALARM_SEVERITY_MAJOR;

            description "
                Describes select operation fails due to timeout or other reason.";

            leaf operation_result {
                type string {
                    pattern '[a-zA-Z0-9]{1}([-a-zA-Z0-9_]{0,31})' {
                        error-message "Invalid select operation failure operation_result.";
                        error-app-tag select-operation-failure-invalid-operation-result;
                    }
                    length 1..32 {
                        error-message "Invalid length for select operation failure operation_result.";
                        error-app-tag select-operation-failure-invalid-operation-result-length;
                    }
                }
                description "Select operation result";
            }

            leaf command {
                type string {
                    pattern '[a-zA-Z0-9]{1}([-a-zA-Z0-9_]{0,31})' {
                        error-message "Invalid select operation failure command.";
                        error-app-tag select-operation-failure-invalid-command;
                    }
                    length 1..32 {
                        error-message "Invalid length for select operation failure command.";
                        error-app-tag select-operation-failure-invalid-command-length;
                    }
                }
                description "Operation command.";
            }

            uses evtcmn:sonic-events-cmn;
        }

        container asic-sdk-health-event {
            evtcmn:ALARM_SEVERITY_MAJOR;
            description
                "Declares an event for ASIC/SDK health event.";
            leaf asic_name {
                type string {
                    pattern 'asic[0-9]{1,2}';
                }
            }
            leaf severity {
                type enumeration {
                    enum fatal;
                    enum warning;
                    enum notice;
                }
            }
            leaf category {
                type enumeration {
                    enum software;
                    enum firmware;
                    enum cpu_hw;
                    enum asic_hw;
                }
            }
            leaf description {
                type string;
            }
            leaf sai_timestamp {
                type string {
                    pattern '[0-9]{4}-[0-9]{2}-[0-9]{2} [0-9]{2}:[0-9]{2}:[0-9]{2}';
                }
            }

            uses evtcmn:sonic-events-cmn;
        }
    }
}
